module cumulus-nclu {
  namespace "http://example.com/cumulus-nclu";
  prefix cumulus;



  revision 2019-11-11 {
    description
      "Initial revision";
  }

  

  container commands {
     leaf-list cmd {
        type string;
     }
  }
}
