submodule device {

    yang-version 1.1;

    belongs-to sno {
        prefix sno;
    }

    import ietf-yang-schema-mount {
        prefix yangmnt;
    }

    import ietf-inet-types { 
        prefix inet; 
    }

    container devices {
        list device {

            key name;

            leaf name {
                type string;
            }

            leaf device_type {
                type enumeration {
                    enum "CumulusLinux";
                    enum "odl";
                }
            }
            leaf mgmt_ip {
                mandatory true;
                type inet:ip-address;
            }

            leaf netconf_port {
                type uint32;
                default 830;
            }

            leaf netconf_user {
                type string;
                default "admin";
            }

            leaf netconf_password {
                type string;
                default "CumulusLinux!";
            }

            container config {
                leaf-list supported-modules {
                    type string;
                }
            }

        }
        list groups {

            key name;

            leaf name {
                type string;
            }

            leaf-list device {
                type leafref {
                    path "../../device/name";
                }
            }
        }
         
    }
}
